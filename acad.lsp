;;;<HOM>*************************************************************************
;;; <ﾌｧｲﾙ名>  : acad.LSP
;;; <ｼｽﾃﾑ名>  : ＮｅｗＰＡＴシステム
;;; <作成>    : 2000/05/22
;;; <備考>    : なし
;;;*************************************************************************>MOH<
;↓これ不要では？コメントしてみた。2015/03/17
;(load (strcat (getvar "PROGRAM") "doc"))
(setq CG_ACAD_INIT   nil) ;AutoCAD起動モード(nil:初期 
(setq CG_STARTUP 0)

(princ "\n★★★ CG_ACAD_INIT = nil")
(princ "\n★★★ CG_STARTUP = 0")

(princ "\n★★★ acad.lspを抜ける")
(princ "\n------------------------------------------")
(princ "\n------------------------------------------")
(princ "\n------------------------------------------")
(princ "\n")
(princ "\n")
(princ "\n")

(princ)
